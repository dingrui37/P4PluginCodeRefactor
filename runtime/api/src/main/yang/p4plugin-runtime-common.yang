module p4plugin-runtime-common {
    yang-version 1;
    namespace "urn:opendaylight:p4plugin:runtime:common";
    prefix "common";

    organization
        "ZTE corporation";

    contact
        "ding.rui@zte.com.cn";

    description
        "This module contains a set of common type definitions
         that are used across p4plugin";

    revision "2017-08-08" {
        description "Initial revision.";
    }

    grouping operation-result {
        leaf code {
            type enumeration {
                enum SUCCESS;
                enum FAILURE;
            }
        }

        leaf message {
            type string;
        }
    }
}
