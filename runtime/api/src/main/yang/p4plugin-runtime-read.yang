module p4plugin-runtime-read {
    yang-version 1;
    namespace "urn:opendaylight:p4plugin:runtime:read";
    prefix "read";

    organization "ZTE corporation";
    contact "ding.rui@zte.com.cn";

    revision "2017-08-08" {
        description "Initial revision.";
    }

    import p4plugin-runtime-types {
        prefix "types";
        revision-date 2017-08-08;
    }

    rpc read-table-entry {
        input {
            uses types:node-id;
            leaf table-name {
                type string;
            }
        }

        output {
            leaf-list entries {
                type string;
            }
        }
    }

    rpc read-action-profile-member {
        input {
            uses types:node-id;
            leaf action-profile-name {
                type string;
            }
        }

        output {
            leaf-list members {
                type string;
            }
        }
    }

    rpc read-action-profile-group {
        input {
            uses types:node-id;
            leaf action-profile-name {
                type string;
            }
        }

        output {
            leaf-list groups {
                type string;
            }
        }
    }
}
