module p4plugin-runtime-member {
    yang-version 1;
    namespace "urn:opendaylight:p4plugin:runtime:member";
    prefix "member";

    organization "ZTE corporation";
    contact "ding.rui@zte.com.cn";

    revision "2017-08-08" {
        description "Initial revision.";
    }

    import p4plugin-runtime-device {
        prefix "device";
        revision-date 2017-08-08;
    }

    import p4plugin-runtime-table {
        prefix "table";
        revision-date 2017-08-08;
    }

    import p4plugin-runtime-types {
        prefix "types";
        revision-date 2017-08-08;
    }

    grouping action-profile-member-key {
        leaf action-profile-name {
            type string;
        }

        leaf member-id {
            type uint32;
        }
    }

    grouping action-profile-member {
        uses action-profile-member-key;
        uses table:action;
    }

    rpc add-action-profile-member {
        input {
            uses device:node-id;
            uses action-profile-member;
        }
    }

    rpc modify-action-profile-member {
        input {
            uses device:node-id;
            uses action-profile-member;
        }
    }

    rpc delete-action-profile-member {
        input {
            uses device:node-id;
            uses action-profile-member-key;
        }
    }

    rpc read-action-profile {
        input {
            uses device:node-id;
            leaf action-profile-name {
                type string;
            }
        }

        output {
            leaf-list members {
                type string;
            }
        }
    }
}
