module p4plugin-runtime-packet {
    yang-version 1;
    namespace "urn:opendaylight:p4plugin:runtime:packet";
    prefix "packet";

    organization "ZTE corporation";
    contact "ding.rui@zte.com.cn";

    revision "2017-08-08" {
        description "Initial revision.";
    }

    import p4plugin-runtime-types {
        prefix "types";
        revision-date 2017-08-08;
    }

    notification p4-packet-received {
        uses types:node-id;
        leaf payload {
            type binary;
        }
    }

    rpc p4-transmit-packet {
        input {
            uses types:node-id;
            leaf payload {
                type binary;
            }
        }
    }
}
