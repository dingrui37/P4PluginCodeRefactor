module p4plugin-runtime-types {
    yang-version 1;
    namespace "urn:opendaylight:p4plugin:runtime:types";
    prefix "types";

    organization "ZTE corporation";
    contact "ding.rui@zte.com.cn";

    revision "2017-08-08" {
        description "Initial revision.";
    }

    import ietf-inet-types {
        prefix "inet";
        revision-date 2013-07-15;
    }

    typedef param-value {
        type union {
            type inet:ipv4-address;
            type mac-address;
            type uint64;
        }
    }

    typedef match-value {
        type union {
            type inet:ipv4-address;
            type mac-address;
            type uint64;
        }
    }

    typedef mac-address {
        type string {
            pattern '[0-9a-fA-F]{2}(:[0-9a-fA-F]{2}){5}';
        }

        description
          "An IEEE 802 MAC address";
    }

    typedef value {
        type string {
            pattern '([0-9a-fA-F]{2}(:[0-9a-fA-F]{2}){5})|'
            + '((([0-9]|[1-9][0-9]|1[0-9][0-9]|2[0-4][0-9]|25[0-5])\.){3}([0-9]|[1-9][0-9]|1[0-9][0-9]|2[0-4][0-9]|25[0-5]))|'
            + '((0x[0-9a-fA-F]+)|([0-9]+))';

        }

        description
          "";
    }

    grouping node-id {
        leaf nid {
            type string;
        }
    }
}
